-- *****************************************************************
-- PORT-POWER-SAVINGS-MIB:  Vitesse private MIB
--
-- Copyright (c) 2002-2013 Vitesse Semiconductor Corporation "Vitesse".
-- All Rights Reserved.
--
-- ****************************************************************

LUXL-PORT-POWER-SAVINGS-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    luxlSwitchMgmt
        FROM LUXL-SMI
    TruthValue FROM SNMPv2-TC
    LUXLInterfaceIndex FROM LUXL-TC
    ;

luxlPortPowerSavingsMib MODULE-IDENTITY
    LAST-UPDATED "201408070000Z"
    ORGANIZATION
        "Vitesse Semiconductor Corporation"
    CONTACT-INFO
        "Application support <application_support@vitesse.com>"
    DESCRIPTION
        "This is a private version of Port Power Saving. Port power saving
         reduces the switch power consumptionby lowering the port power supply
         when there is no link partner connected to a port as well as when link
         partner is connected through a short cable."
    REVISION    "201408070000Z"
    DESCRIPTION
        "Initial version"
    ::= { luxlSwitchMgmt 100 }


LUXLPortPowerSavingsStatusType ::= TEXTUAL-CONVENTION
    STATUS      current
    DESCRIPTION
        "This enumeration defines the feature status."
    SYNTAX      INTEGER { no(0), yes(1), notSupported(2) }

luxlPortPowerSavingsMibObjects OBJECT IDENTIFIER
    ::= { luxlPortPowerSavingsMib 1 }

luxlPortPowerSavingsCapabilities OBJECT IDENTIFIER
    ::= { luxlPortPowerSavingsMibObjects 1 }

luxlPortPowerSavingsCapabilitiesInterfaceTable OBJECT-TYPE
    SYNTAX      SEQUENCE OF LUXLPortPowerSavingsCapabilitiesInterfaceEntry
    MAX-ACCESS  not-accessible
    STATUS      current
    DESCRIPTION 
        "This is a table to interface capabilities"
    ::= { luxlPortPowerSavingsCapabilities 1 }

luxlPortPowerSavingsCapabilitiesInterfaceEntry OBJECT-TYPE
    SYNTAX      LUXLPortPowerSavingsCapabilitiesInterfaceEntry
    MAX-ACCESS  not-accessible
    STATUS      current
    DESCRIPTION 
        "Each interface has a set of capability parameters"
    INDEX       { luxlPortPowerSavingsCapabilitiesInterfaceIfIndex }
    ::= { luxlPortPowerSavingsCapabilitiesInterfaceTable 1 }

LUXLPortPowerSavingsCapabilitiesInterfaceEntry ::= SEQUENCE {
    luxlPortPowerSavingsCapabilitiesInterfaceIfIndex    LUXLInterfaceIndex,
    luxlPortPowerSavingsCapabilitiesInterfaceLinkPartner    TruthValue,
    luxlPortPowerSavingsCapabilitiesInterfaceShortReach     TruthValue
}

luxlPortPowerSavingsCapabilitiesInterfaceIfIndex OBJECT-TYPE
    SYNTAX      LUXLInterfaceIndex
    MAX-ACCESS  not-accessible
    STATUS      current
    DESCRIPTION 
        "Logical interface number."
    ::= { luxlPortPowerSavingsCapabilitiesInterfaceEntry 1 }

luxlPortPowerSavingsCapabilitiesInterfaceLinkPartner OBJECT-TYPE
    SYNTAX      TruthValue
    MAX-ACCESS  read-only
    STATUS      current
    DESCRIPTION 
        "Indicate whether interface is capable for detecting link partner or
         not. true means interface is capable to detect link partner, false
         means interface is not capable to detect link partner."
    ::= { luxlPortPowerSavingsCapabilitiesInterfaceEntry 2 }

luxlPortPowerSavingsCapabilitiesInterfaceShortReach OBJECT-TYPE
    SYNTAX      TruthValue
    MAX-ACCESS  read-only
    STATUS      current
    DESCRIPTION 
        "Indicates whether interface is able to determine the cable length
         connected to partner port. true means interface is capable to determine
         the cable length, false means interface is not capable to determine the
         cable length."
    ::= { luxlPortPowerSavingsCapabilitiesInterfaceEntry 3 }

luxlPortPowerSavingsConfig OBJECT IDENTIFIER
    ::= { luxlPortPowerSavingsMibObjects 2 }

luxlPortPowerSavingsConfigInterfaceParamTable OBJECT-TYPE
    SYNTAX      SEQUENCE OF LUXLPortPowerSavingsConfigInterfaceParamEntry
    MAX-ACCESS  not-accessible
    STATUS      current
    DESCRIPTION 
        "This table provides Port Power Savings configuration for an interface"
    ::= { luxlPortPowerSavingsConfig 1 }

luxlPortPowerSavingsConfigInterfaceParamEntry OBJECT-TYPE
    SYNTAX      LUXLPortPowerSavingsConfigInterfaceParamEntry
    MAX-ACCESS  not-accessible
    STATUS      current
    DESCRIPTION 
        "Each interface has a set of Port Power Savings configurable parameters"
    INDEX       { luxlPortPowerSavingsConfigInterfaceParamIfIndex }
    ::= { luxlPortPowerSavingsConfigInterfaceParamTable 1 }

LUXLPortPowerSavingsConfigInterfaceParamEntry ::= SEQUENCE {
    luxlPortPowerSavingsConfigInterfaceParamIfIndex     LUXLInterfaceIndex,
    luxlPortPowerSavingsConfigInterfaceParamLinkPartner     TruthValue,
    luxlPortPowerSavingsConfigInterfaceParamShortReach      TruthValue
}

luxlPortPowerSavingsConfigInterfaceParamIfIndex OBJECT-TYPE
    SYNTAX      LUXLInterfaceIndex
    MAX-ACCESS  not-accessible
    STATUS      current
    DESCRIPTION 
        "Logical interface number."
    ::= { luxlPortPowerSavingsConfigInterfaceParamEntry 1 }

luxlPortPowerSavingsConfigInterfaceParamLinkPartner OBJECT-TYPE
    SYNTAX      TruthValue
    MAX-ACCESS  read-write
    STATUS      current
    DESCRIPTION 
        "Save port power if there is no link partner connected to the port. true
         is to enable port power saving when there is no link partner connected,
         false is to disable it."
    ::= { luxlPortPowerSavingsConfigInterfaceParamEntry 2 }

luxlPortPowerSavingsConfigInterfaceParamShortReach OBJECT-TYPE
    SYNTAX      TruthValue
    MAX-ACCESS  read-write
    STATUS      current
    DESCRIPTION 
        "Save port power if port is connected to link partner through short
         cable. true is to enable port power saving when link partner connected
         through short cable, false is to disable it."
    ::= { luxlPortPowerSavingsConfigInterfaceParamEntry 3 }

luxlPortPowerSavingsStatus OBJECT IDENTIFIER
    ::= { luxlPortPowerSavingsMibObjects 3 }

luxlPortPowerSavingsStatusInterfaceTable OBJECT-TYPE
    SYNTAX      SEQUENCE OF LUXLPortPowerSavingsStatusInterfaceEntry
    MAX-ACCESS  not-accessible
    STATUS      current
    DESCRIPTION 
        "This is a table to Port Power Savings interface status"
    ::= { luxlPortPowerSavingsStatus 1 }

luxlPortPowerSavingsStatusInterfaceEntry OBJECT-TYPE
    SYNTAX      LUXLPortPowerSavingsStatusInterfaceEntry
    MAX-ACCESS  not-accessible
    STATUS      current
    DESCRIPTION 
        "Each interface has a set of status parameters"
    INDEX       { luxlPortPowerSavingsStatusInterfaceIfIndex }
    ::= { luxlPortPowerSavingsStatusInterfaceTable 1 }

LUXLPortPowerSavingsStatusInterfaceEntry ::= SEQUENCE {
    luxlPortPowerSavingsStatusInterfaceIfIndex      LUXLInterfaceIndex,
    luxlPortPowerSavingsStatusInterfaceNoLinkPartner    LUXLPortPowerSavingsStatusType,
    luxlPortPowerSavingsStatusInterfaceShortCable   LUXLPortPowerSavingsStatusType
}

luxlPortPowerSavingsStatusInterfaceIfIndex OBJECT-TYPE
    SYNTAX      LUXLInterfaceIndex
    MAX-ACCESS  not-accessible
    STATUS      current
    DESCRIPTION 
        "Logical interface number."
    ::= { luxlPortPowerSavingsStatusInterfaceEntry 1 }

luxlPortPowerSavingsStatusInterfaceNoLinkPartner OBJECT-TYPE
    SYNTAX      LUXLPortPowerSavingsStatusType
    MAX-ACCESS  read-only
    STATUS      current
    DESCRIPTION 
        "Indicate whether port is saving power due to no link partner connected."
    ::= { luxlPortPowerSavingsStatusInterfaceEntry 2 }

luxlPortPowerSavingsStatusInterfaceShortCable OBJECT-TYPE
    SYNTAX      LUXLPortPowerSavingsStatusType
    MAX-ACCESS  read-only
    STATUS      current
    DESCRIPTION 
        "Indicate whether port is saving power due to link partner connected
         through short cable."
    ::= { luxlPortPowerSavingsStatusInterfaceEntry 3 }

luxlPortPowerSavingsMibConformance OBJECT IDENTIFIER
    ::= { luxlPortPowerSavingsMib 2 }

luxlPortPowerSavingsMibCompliances OBJECT IDENTIFIER
    ::= { luxlPortPowerSavingsMibConformance 1 }

luxlPortPowerSavingsMibGroups OBJECT IDENTIFIER
    ::= { luxlPortPowerSavingsMibConformance 2 }

luxlPortPowerSavingsCapabilitiesInterfaceInfoGroup OBJECT-GROUP
    OBJECTS     { luxlPortPowerSavingsCapabilitiesInterfaceLinkPartner, 
                  luxlPortPowerSavingsCapabilitiesInterfaceShortReach }
    STATUS      current
    DESCRIPTION
        "A collection of objects suitable for bulk operations."
    ::= { luxlPortPowerSavingsMibGroups 1 }

luxlPortPowerSavingsConfigInterfaceParamTableInfoGroup OBJECT-GROUP
    OBJECTS     { luxlPortPowerSavingsConfigInterfaceParamLinkPartner, 
                  luxlPortPowerSavingsConfigInterfaceParamShortReach }
    STATUS      current
    DESCRIPTION
        "A collection of objects suitable for bulk operations."
    ::= { luxlPortPowerSavingsMibGroups 2 }

luxlPortPowerSavingsStatusInterfaceTableInfoGroup OBJECT-GROUP
    OBJECTS     { luxlPortPowerSavingsStatusInterfaceNoLinkPartner, 
                  luxlPortPowerSavingsStatusInterfaceShortCable }
    STATUS      current
    DESCRIPTION
        "A collection of objects suitable for bulk operations."
    ::= { luxlPortPowerSavingsMibGroups 3 }

luxlPortPowerSavingsMibCompliance MODULE-COMPLIANCE
    STATUS      current
    DESCRIPTION
        "The compliance statement for the implementation."

    MODULE      -- this module

        MANDATORY-GROUPS        { 
                  luxlPortPowerSavingsCapabilitiesInterfaceInfoGroup, 
                  luxlPortPowerSavingsConfigInterfaceParamTableInfoGroup, 
                  luxlPortPowerSavingsStatusInterfaceTableInfoGroup }

    ::= { luxlPortPowerSavingsMibCompliances 1 }

END
