-- *****************************************************************
-- VLAN-TRANSLATION-MIB:  Vitesse private MIB
--
-- Copyright (c) 2002-2013 Vitesse Semiconductor Corporation "Vitesse".
-- All Rights Reserved.
--
-- ****************************************************************

LUXL-VLAN-TRANSLATION-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    luxlSwitchMgmt
        FROM LUXL-SMI
    Integer32 FROM SNMPv2-SMI
    Unsigned32 FROM SNMPv2-SMI
    LUXLInterfaceIndex FROM LUXL-TC
    LUXLRowEditorState FROM LUXL-TC
    ;

luxlVlanTranslationMib MODULE-IDENTITY
    LAST-UPDATED "201406300000Z"
    ORGANIZATION
        "Vitesse Semiconductor Corporation"
    CONTACT-INFO
        "Application support <application_support@vitesse.com>"
    DESCRIPTION
        "Private VLAN TRANSLATION MIB."
    REVISION    "201406300000Z"
    DESCRIPTION
        "Initial version"
    ::= { luxlSwitchMgmt 85 }


luxlVlanTranslationMibObjects OBJECT IDENTIFIER
    ::= { luxlVlanTranslationMib 1 }

luxlVlanTranslationCapabilities OBJECT IDENTIFIER
    ::= { luxlVlanTranslationMibObjects 1 }

luxlVlanTranslationCapabilitiesMaxNumberOfTranslations OBJECT-TYPE
    SYNTAX      Unsigned32
    MAX-ACCESS  read-only
    STATUS      current
    DESCRIPTION 
        "Maximum number of VLAN translation mappings the user can store in the
         VLAN Translation mapping table."
    ::= { luxlVlanTranslationCapabilities 1 }

luxlVlanTranslationConfig OBJECT IDENTIFIER
    ::= { luxlVlanTranslationMibObjects 2 }

luxlVlanTranslationConfigTranslation OBJECT IDENTIFIER
    ::= { luxlVlanTranslationConfig 1 }

luxlVlanTranslationConfigTranslationTable OBJECT-TYPE
    SYNTAX      SEQUENCE OF LUXLVlanTranslationConfigTranslationEntry
    MAX-ACCESS  not-accessible
    STATUS      current
    DESCRIPTION 
        "This is the VLAN translation mapping table.
         
         Here the user stores VLAN translation mappings (VID->TVID) inside
         groups that can later be activated on specific switch interfaces"
    ::= { luxlVlanTranslationConfigTranslation 1 }

luxlVlanTranslationConfigTranslationEntry OBJECT-TYPE
    SYNTAX      LUXLVlanTranslationConfigTranslationEntry
    MAX-ACCESS  not-accessible
    STATUS      current
    DESCRIPTION 
        "Each entry in this table represents a VLAN translation mapping stored
         inside a specific VLAN translation Group.
         
         The entry key is the Group ID and the source VLAN ID, while the value
         is the translated VID.
         
         "
    INDEX       { luxlVlanTranslationConfigTranslationGroupId, luxlVlanTranslationConfigTranslationVlanId }
    ::= { luxlVlanTranslationConfigTranslationTable 1 }

LUXLVlanTranslationConfigTranslationEntry ::= SEQUENCE {
    luxlVlanTranslationConfigTranslationGroupId     Integer32,
    luxlVlanTranslationConfigTranslationVlanId      Integer32,
    luxlVlanTranslationConfigTranslationTVlanId     Integer32,
    luxlVlanTranslationConfigTranslationAction      LUXLRowEditorState
}

luxlVlanTranslationConfigTranslationGroupId OBJECT-TYPE
    SYNTAX      Integer32 (1..65535)
    MAX-ACCESS  not-accessible
    STATUS      current
    DESCRIPTION 
        "Group ID of the VLAN translation mapping key."
    ::= { luxlVlanTranslationConfigTranslationEntry 1 }

luxlVlanTranslationConfigTranslationVlanId OBJECT-TYPE
    SYNTAX      Integer32 (1..4095)
    MAX-ACCESS  not-accessible
    STATUS      current
    DESCRIPTION 
        "Vlan ID of the VLAN translation mapping key."
    ::= { luxlVlanTranslationConfigTranslationEntry 2 }

luxlVlanTranslationConfigTranslationTVlanId OBJECT-TYPE
    SYNTAX      Integer32 (1..4095)
    MAX-ACCESS  read-write
    STATUS      current
    DESCRIPTION 
        "Translated VLAN ID of the VLAN translation mapping."
    ::= { luxlVlanTranslationConfigTranslationEntry 3 }

luxlVlanTranslationConfigTranslationAction OBJECT-TYPE
    SYNTAX      LUXLRowEditorState
    MAX-ACCESS  read-write
    STATUS      current
    DESCRIPTION 
        "Action"
    ::= { luxlVlanTranslationConfigTranslationEntry 100 }

luxlVlanTranslationConfigTranslationRowEditor OBJECT IDENTIFIER
    ::= { luxlVlanTranslationConfigTranslation 2 }

luxlVlanTranslationConfigTranslationRowEditorGroupId OBJECT-TYPE
    SYNTAX      Integer32 (1..65535)
    MAX-ACCESS  read-write
    STATUS      current
    DESCRIPTION 
        "Group ID of the VLAN translation mapping key."
    ::= { luxlVlanTranslationConfigTranslationRowEditor 1 }

luxlVlanTranslationConfigTranslationRowEditorVlanId OBJECT-TYPE
    SYNTAX      Integer32 (1..4095)
    MAX-ACCESS  read-write
    STATUS      current
    DESCRIPTION 
        "Vlan ID of the VLAN translation mapping key."
    ::= { luxlVlanTranslationConfigTranslationRowEditor 2 }

luxlVlanTranslationConfigTranslationRowEditorTVlanId OBJECT-TYPE
    SYNTAX      Integer32 (1..4095)
    MAX-ACCESS  read-write
    STATUS      current
    DESCRIPTION 
        "Translated VLAN ID of the VLAN translation mapping."
    ::= { luxlVlanTranslationConfigTranslationRowEditor 3 }

luxlVlanTranslationConfigTranslationRowEditorAction OBJECT-TYPE
    SYNTAX      LUXLRowEditorState
    MAX-ACCESS  read-write
    STATUS      current
    DESCRIPTION 
        "Action"
    ::= { luxlVlanTranslationConfigTranslationRowEditor 100 }

luxlVlanTranslationConfigInterfaces OBJECT IDENTIFIER
    ::= { luxlVlanTranslationConfig 2 }

luxlVlanTranslationConfigInterfacesIfTable OBJECT-TYPE
    SYNTAX      SEQUENCE OF LUXLVlanTranslationConfigInterfacesIfEntry
    MAX-ACCESS  not-accessible
    STATUS      current
    DESCRIPTION 
        "This is the VLAN translation interface table. The number of interfaces
         is the total number of ports available on the switch. Each one of these
         interfaces can be set to use a specific Group of VLAN translation
         mappings, identified by the respective Group ID."
    ::= { luxlVlanTranslationConfigInterfaces 1 }

luxlVlanTranslationConfigInterfacesIfEntry OBJECT-TYPE
    SYNTAX      LUXLVlanTranslationConfigInterfacesIfEntry
    MAX-ACCESS  not-accessible
    STATUS      current
    DESCRIPTION 
        "Entries in this table represent switch interfaces and their matching
         VLAN translation Groups (identified through their Group IDs)"
    INDEX       { luxlVlanTranslationConfigInterfacesIfIfIndex }
    ::= { luxlVlanTranslationConfigInterfacesIfTable 1 }

LUXLVlanTranslationConfigInterfacesIfEntry ::= SEQUENCE {
    luxlVlanTranslationConfigInterfacesIfIfIndex    LUXLInterfaceIndex,
    luxlVlanTranslationConfigInterfacesIfGroupId    Integer32
}

luxlVlanTranslationConfigInterfacesIfIfIndex OBJECT-TYPE
    SYNTAX      LUXLInterfaceIndex
    MAX-ACCESS  not-accessible
    STATUS      current
    DESCRIPTION 
        "Interface index number."
    ::= { luxlVlanTranslationConfigInterfacesIfEntry 1 }

luxlVlanTranslationConfigInterfacesIfGroupId OBJECT-TYPE
    SYNTAX      Integer32 (1..65535)
    MAX-ACCESS  read-write
    STATUS      current
    DESCRIPTION 
        "Group ID of the interface configuration."
    ::= { luxlVlanTranslationConfigInterfacesIfEntry 2 }

luxlVlanTranslationMibConformance OBJECT IDENTIFIER
    ::= { luxlVlanTranslationMib 2 }

luxlVlanTranslationMibCompliances OBJECT IDENTIFIER
    ::= { luxlVlanTranslationMibConformance 1 }

luxlVlanTranslationMibGroups OBJECT IDENTIFIER
    ::= { luxlVlanTranslationMibConformance 2 }

luxlVlanTranslationCapabilitiesInfoGroup OBJECT-GROUP
    OBJECTS     { luxlVlanTranslationCapabilitiesMaxNumberOfTranslations }
    STATUS      current
    DESCRIPTION
        "A collection of objects suitable for bulk operations."
    ::= { luxlVlanTranslationMibGroups 1 }

luxlVlanTranslationConfigTranslationTableInfoGroup OBJECT-GROUP
    OBJECTS     { luxlVlanTranslationConfigTranslationTVlanId, 
                  luxlVlanTranslationConfigTranslationAction }
    STATUS      current
    DESCRIPTION
        "A collection of objects suitable for bulk operations."
    ::= { luxlVlanTranslationMibGroups 2 }

luxlVlanTranslationConfigTranslationRowEditorInfoGroup OBJECT-GROUP
    OBJECTS     { luxlVlanTranslationConfigTranslationRowEditorGroupId, 
                  luxlVlanTranslationConfigTranslationRowEditorVlanId, 
                  luxlVlanTranslationConfigTranslationRowEditorTVlanId, 
                  luxlVlanTranslationConfigTranslationRowEditorAction }
    STATUS      current
    DESCRIPTION
        "A collection of objects suitable for bulk operations."
    ::= { luxlVlanTranslationMibGroups 3 }

luxlVlanTranslationConfigInterfacesIfTableInfoGroup OBJECT-GROUP
    OBJECTS     { luxlVlanTranslationConfigInterfacesIfGroupId }
    STATUS      current
    DESCRIPTION
        "A collection of objects suitable for bulk operations."
    ::= { luxlVlanTranslationMibGroups 4 }

luxlVlanTranslationMibCompliance MODULE-COMPLIANCE
    STATUS      current
    DESCRIPTION
        "The compliance statement for the implementation."

    MODULE      -- this module

        MANDATORY-GROUPS        { luxlVlanTranslationCapabilitiesInfoGroup, 
                  luxlVlanTranslationConfigTranslationTableInfoGroup, 
                  luxlVlanTranslationConfigTranslationRowEditorInfoGroup, 
                  luxlVlanTranslationConfigInterfacesIfTableInfoGroup }

    ::= { luxlVlanTranslationMibCompliances 1 }

END
