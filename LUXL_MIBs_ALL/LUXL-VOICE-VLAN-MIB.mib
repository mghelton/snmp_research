-- *****************************************************************
-- VOICE-VLAN-MIB:  Vitesse private MIB
--
-- Copyright (c) 2002-2013 Vitesse Semiconductor Corporation "Vitesse".
-- All Rights Reserved.
--
-- ****************************************************************

LUXL-VOICE-VLAN-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    luxlSwitchMgmt
        FROM LUXL-SMI
    Unsigned32 FROM SNMPv2-SMI
    TruthValue FROM SNMPv2-TC
    LUXLDisplayString FROM LUXL-TC
    LUXLInterfaceIndex FROM LUXL-TC
    LUXLRowEditorState FROM LUXL-TC
    LUXLUnsigned16 FROM LUXL-TC
    ;

luxlVoiceVlanMib MODULE-IDENTITY
    LAST-UPDATED "201409160000Z"
    ORGANIZATION
        "Vitesse Semiconductor Corporation"
    CONTACT-INFO
        "Application support <application_support@vitesse.com>"
    DESCRIPTION
        "This is a private version of the Voice VLAN MIB."
    REVISION    "201409160000Z"
    DESCRIPTION
        "Initial version."
    ::= { luxlSwitchMgmt 70 }


LUXLVoiceVlanPortDiscoveryProtocol ::= TEXTUAL-CONVENTION
    STATUS      current
    DESCRIPTION
        "This enumeration indicates per port Voice VLAN discovery protocol."
    SYNTAX      INTEGER { oui(0), lldp(1), both(2) }

LUXLVoiceVlanPortManagementType ::= TEXTUAL-CONVENTION
    STATUS      current
    DESCRIPTION
        "This enumeration indicates per port Voice VLAN function administrative
         type."
    SYNTAX      INTEGER { disabled(0), forced(1), automatic(2) }

luxlVoiceVlanMibObjects OBJECT IDENTIFIER
    ::= { luxlVoiceVlanMib 1 }

luxlVoiceVlanCapabilities OBJECT IDENTIFIER
    ::= { luxlVoiceVlanMibObjects 1 }

luxlVoiceVlanCapabilitiesSupportLldpDiscovery OBJECT-TYPE
    SYNTAX      TruthValue
    MAX-ACCESS  read-only
    STATUS      current
    DESCRIPTION 
        "The capability to support voice device discovery from LLDP
         notification."
    ::= { luxlVoiceVlanCapabilities 1 }

luxlVoiceVlanCapabilitiesMinAgeTime OBJECT-TYPE
    SYNTAX      Unsigned32
    MAX-ACCESS  read-only
    STATUS      current
    DESCRIPTION 
        "The minimum time value in second for aging telephony OUI sources in
         voice VLAN."
    ::= { luxlVoiceVlanCapabilities 2 }

luxlVoiceVlanCapabilitiesMaxAgeTime OBJECT-TYPE
    SYNTAX      Unsigned32
    MAX-ACCESS  read-only
    STATUS      current
    DESCRIPTION 
        "The maximum time value in second for aging telephony OUI sources in
         voice VLAN."
    ::= { luxlVoiceVlanCapabilities 3 }

luxlVoiceVlanCapabilitiesMaxTrafficClass OBJECT-TYPE
    SYNTAX      Unsigned32
    MAX-ACCESS  read-only
    STATUS      current
    DESCRIPTION 
        "The maximum allowed CoS (Class of Service) value to be used in
         forwarding voice VLAN traffic."
    ::= { luxlVoiceVlanCapabilities 4 }

luxlVoiceVlanCapabilitiesMaxOuiEntryCount OBJECT-TYPE
    SYNTAX      Unsigned32
    MAX-ACCESS  read-only
    STATUS      current
    DESCRIPTION 
        "The maximum number of telephony OUI entry registration."
    ::= { luxlVoiceVlanCapabilities 5 }

luxlVoiceVlanConfig OBJECT IDENTIFIER
    ::= { luxlVoiceVlanMibObjects 2 }

luxlVoiceVlanConfigGlobals OBJECT IDENTIFIER
    ::= { luxlVoiceVlanConfig 1 }

luxlVoiceVlanConfigGlobalsMgmt OBJECT IDENTIFIER
    ::= { luxlVoiceVlanConfigGlobals 1 }

luxlVoiceVlanConfigGlobalsMgmtAdminState OBJECT-TYPE
    SYNTAX      TruthValue
    MAX-ACCESS  read-write
    STATUS      current
    DESCRIPTION 
        "Administrative control for system wide voice VLAN function, TRUE is to
         enable the voice VLAN function and FALSE is to disable it."
    ::= { luxlVoiceVlanConfigGlobalsMgmt 1 }

luxlVoiceVlanConfigGlobalsMgmtVlanId OBJECT-TYPE
    SYNTAX      LUXLUnsigned16
    MAX-ACCESS  read-write
    STATUS      current
    DESCRIPTION 
        "VLAN ID, which should be unique in the system, for voice VLAN."
    ::= { luxlVoiceVlanConfigGlobalsMgmt 2 }

luxlVoiceVlanConfigGlobalsMgmtAgingTime OBJECT-TYPE
    SYNTAX      Unsigned32
    MAX-ACCESS  read-write
    STATUS      current
    DESCRIPTION 
        "MAC address aging time (T) for telephony OUI source registrated by
         voice VLAN. The actual timing in purging the specific entry ranges from
         T to 2T."
    ::= { luxlVoiceVlanConfigGlobalsMgmt 3 }

luxlVoiceVlanConfigGlobalsMgmtTrafficClass OBJECT-TYPE
    SYNTAX      Unsigned32
    MAX-ACCESS  read-write
    STATUS      current
    DESCRIPTION 
        "Traffic class value used in frame CoS queuing insides voice VLAN. All
         kinds of traffic on voice VLAN apply this traffic class."
    ::= { luxlVoiceVlanConfigGlobalsMgmt 4 }

luxlVoiceVlanConfigInterface OBJECT IDENTIFIER
    ::= { luxlVoiceVlanConfig 2 }

luxlVoiceVlanConfigInterfacePortTable OBJECT-TYPE
    SYNTAX      SEQUENCE OF LUXLVoiceVlanConfigInterfacePortEntry
    MAX-ACCESS  not-accessible
    STATUS      current
    DESCRIPTION 
        "This is a table for managing per port voice VLAN functions."
    ::= { luxlVoiceVlanConfigInterface 1 }

luxlVoiceVlanConfigInterfacePortEntry OBJECT-TYPE
    SYNTAX      LUXLVoiceVlanConfigInterfacePortEntry
    MAX-ACCESS  not-accessible
    STATUS      current
    DESCRIPTION 
        "Each entry has a set of parameters."
    INDEX       { luxlVoiceVlanConfigInterfacePortIfIndex }
    ::= { luxlVoiceVlanConfigInterfacePortTable 1 }

LUXLVoiceVlanConfigInterfacePortEntry ::= SEQUENCE {
    luxlVoiceVlanConfigInterfacePortIfIndex     LUXLInterfaceIndex,
    luxlVoiceVlanConfigInterfacePortMode    LUXLVoiceVlanPortManagementType,
    luxlVoiceVlanConfigInterfacePortDiscoveryProtocol   LUXLVoiceVlanPortDiscoveryProtocol,
    luxlVoiceVlanConfigInterfacePortSecured     TruthValue
}

luxlVoiceVlanConfigInterfacePortIfIndex OBJECT-TYPE
    SYNTAX      LUXLInterfaceIndex
    MAX-ACCESS  not-accessible
    STATUS      current
    DESCRIPTION 
        "Logical interface number of the Voice VLAN port."
    ::= { luxlVoiceVlanConfigInterfacePortEntry 1 }

luxlVoiceVlanConfigInterfacePortMode OBJECT-TYPE
    SYNTAX      LUXLVoiceVlanPortManagementType
    MAX-ACCESS  read-write
    STATUS      current
    DESCRIPTION 
        "Management mode of the specific port in voice VLAN. 'disabled' will
         disjoin the port from voice VLAN. 'forced' will force the port to join
         voice VLAN. 'automatic' will join the port in voice VLAN upon detecting
         attached VoIP devices by using DiscoveryProtocol parameter."
    ::= { luxlVoiceVlanConfigInterfacePortEntry 2 }

luxlVoiceVlanConfigInterfacePortDiscoveryProtocol OBJECT-TYPE
    SYNTAX      LUXLVoiceVlanPortDiscoveryProtocol
    MAX-ACCESS  read-write
    STATUS      current
    DESCRIPTION 
        "Specify the protocol for detecting attached VoIP devices. It only works
         when 'automatic' is set in Mode parameter, and voice VLAN will restart
         automatic detecting process upon changing the protocol. When 'oui' is
         given, voice VLAN performs VoIP device detection based on checking
         telephony OUI settings via new MAC address notification. When 'lldp' is
         given, voice VLAN performs VoIP device detection based on LLDP
         notifications.When 'both' is given, voice VLAN performs VoIP device
         detection based on either new MAC address notification or LLDP
         notifications.
         
         In addition, the first come notification will be first served."
    ::= { luxlVoiceVlanConfigInterfacePortEntry 3 }

luxlVoiceVlanConfigInterfacePortSecured OBJECT-TYPE
    SYNTAX      TruthValue
    MAX-ACCESS  read-write
    STATUS      current
    DESCRIPTION 
        "Manage the security control of this port interface in voice VLAN, TRUE
         is to enable the security control and FALSE is to disable it. When it
         is disabled, all the traffic in voice VLAN will be permit. When it is
         enabled, all non-telephonic MAC addresses in the voice VLAN will be
         blocked for 10 seconds and thus the traffic from these senders will be
         deny."
    ::= { luxlVoiceVlanConfigInterfacePortEntry 4 }

luxlVoiceVlanConfigOui OBJECT IDENTIFIER
    ::= { luxlVoiceVlanConfig 3 }

luxlVoiceVlanConfigOuiTable OBJECT-TYPE
    SYNTAX      SEQUENCE OF LUXLVoiceVlanConfigOuiEntry
    MAX-ACCESS  not-accessible
    STATUS      current
    DESCRIPTION 
        "This is a table for managing the telephony OUI settings that will be
         used for voice VLAN functions."
    ::= { luxlVoiceVlanConfigOui 1 }

luxlVoiceVlanConfigOuiEntry OBJECT-TYPE
    SYNTAX      LUXLVoiceVlanConfigOuiEntry
    MAX-ACCESS  not-accessible
    STATUS      current
    DESCRIPTION 
        "Each entry has a set of parameters."
    INDEX       { luxlVoiceVlanConfigOuiPrefix }
    ::= { luxlVoiceVlanConfigOuiTable 1 }

LUXLVoiceVlanConfigOuiEntry ::= SEQUENCE {
    luxlVoiceVlanConfigOuiPrefix    OCTET STRING,
    luxlVoiceVlanConfigOuiDescription   LUXLDisplayString,
    luxlVoiceVlanConfigOuiAction    LUXLRowEditorState
}

luxlVoiceVlanConfigOuiPrefix OBJECT-TYPE
    SYNTAX      OCTET STRING (SIZE(3..3))
    MAX-ACCESS  not-accessible
    STATUS      current
    DESCRIPTION 
        "Address prefix of the telephony OUI. A leading 3 bytes index used to
         denote whether specific MAC address is presenting a voice device."
    ::= { luxlVoiceVlanConfigOuiEntry 1 }

luxlVoiceVlanConfigOuiDescription OBJECT-TYPE
    SYNTAX      LUXLDisplayString (SIZE(0..32))
    MAX-ACCESS  read-write
    STATUS      current
    DESCRIPTION 
        "The description for the specific telephony OUI."
    ::= { luxlVoiceVlanConfigOuiEntry 2 }

luxlVoiceVlanConfigOuiAction OBJECT-TYPE
    SYNTAX      LUXLRowEditorState
    MAX-ACCESS  read-write
    STATUS      current
    DESCRIPTION 
        "Action"
    ::= { luxlVoiceVlanConfigOuiEntry 100 }

luxlVoiceVlanConfigOuiTableRowEditor OBJECT IDENTIFIER
    ::= { luxlVoiceVlanConfigOui 2 }

luxlVoiceVlanConfigOuiTableRowEditorPrefix OBJECT-TYPE
    SYNTAX      OCTET STRING (SIZE(3..3))
    MAX-ACCESS  read-write
    STATUS      current
    DESCRIPTION 
        "Address prefix of the telephony OUI. A leading 3 bytes index used to
         denote whether specific MAC address is presenting a voice device."
    ::= { luxlVoiceVlanConfigOuiTableRowEditor 1 }

luxlVoiceVlanConfigOuiTableRowEditorDescription OBJECT-TYPE
    SYNTAX      LUXLDisplayString (SIZE(0..32))
    MAX-ACCESS  read-write
    STATUS      current
    DESCRIPTION 
        "The description for the specific telephony OUI."
    ::= { luxlVoiceVlanConfigOuiTableRowEditor 2 }

luxlVoiceVlanConfigOuiTableRowEditorAction OBJECT-TYPE
    SYNTAX      LUXLRowEditorState
    MAX-ACCESS  read-write
    STATUS      current
    DESCRIPTION 
        "Action"
    ::= { luxlVoiceVlanConfigOuiTableRowEditor 100 }

luxlVoiceVlanMibConformance OBJECT IDENTIFIER
    ::= { luxlVoiceVlanMib 2 }

luxlVoiceVlanMibCompliances OBJECT IDENTIFIER
    ::= { luxlVoiceVlanMibConformance 1 }

luxlVoiceVlanMibGroups OBJECT IDENTIFIER
    ::= { luxlVoiceVlanMibConformance 2 }

luxlVoiceVlanCapabilitiesInfoGroup OBJECT-GROUP
    OBJECTS     { luxlVoiceVlanCapabilitiesSupportLldpDiscovery, 
                  luxlVoiceVlanCapabilitiesMinAgeTime, 
                  luxlVoiceVlanCapabilitiesMaxAgeTime, 
                  luxlVoiceVlanCapabilitiesMaxTrafficClass, 
                  luxlVoiceVlanCapabilitiesMaxOuiEntryCount }
    STATUS      current
    DESCRIPTION
        "A collection of objects suitable for bulk operations."
    ::= { luxlVoiceVlanMibGroups 1 }

luxlVoiceVlanConfigGlobalsMgmtInfoGroup OBJECT-GROUP
    OBJECTS     { luxlVoiceVlanConfigGlobalsMgmtAdminState, 
                  luxlVoiceVlanConfigGlobalsMgmtVlanId, 
                  luxlVoiceVlanConfigGlobalsMgmtAgingTime, 
                  luxlVoiceVlanConfigGlobalsMgmtTrafficClass }
    STATUS      current
    DESCRIPTION
        "A collection of objects suitable for bulk operations."
    ::= { luxlVoiceVlanMibGroups 2 }

luxlVoiceVlanConfigInterfacePortTableInfoGroup OBJECT-GROUP
    OBJECTS     { luxlVoiceVlanConfigInterfacePortMode, 
                  luxlVoiceVlanConfigInterfacePortDiscoveryProtocol, 
                  luxlVoiceVlanConfigInterfacePortSecured }
    STATUS      current
    DESCRIPTION
        "A collection of objects suitable for bulk operations."
    ::= { luxlVoiceVlanMibGroups 3 }

luxlVoiceVlanConfigOuiTableInfoGroup OBJECT-GROUP
    OBJECTS     { luxlVoiceVlanConfigOuiDescription, 
                  luxlVoiceVlanConfigOuiAction }
    STATUS      current
    DESCRIPTION
        "A collection of objects suitable for bulk operations."
    ::= { luxlVoiceVlanMibGroups 4 }

luxlVoiceVlanConfigOuiTableRowEditorInfoGroup OBJECT-GROUP
    OBJECTS     { luxlVoiceVlanConfigOuiTableRowEditorPrefix, 
                  luxlVoiceVlanConfigOuiTableRowEditorDescription, 
                  luxlVoiceVlanConfigOuiTableRowEditorAction }
    STATUS      current
    DESCRIPTION
        "A collection of objects suitable for bulk operations."
    ::= { luxlVoiceVlanMibGroups 5 }

luxlVoiceVlanMibCompliance MODULE-COMPLIANCE
    STATUS      current
    DESCRIPTION
        "The compliance statement for the implementation."

    MODULE      -- this module

        MANDATORY-GROUPS        { luxlVoiceVlanCapabilitiesInfoGroup, 
                  luxlVoiceVlanConfigGlobalsMgmtInfoGroup, 
                  luxlVoiceVlanConfigInterfacePortTableInfoGroup, 
                  luxlVoiceVlanConfigOuiTableInfoGroup, 
                  luxlVoiceVlanConfigOuiTableRowEditorInfoGroup }

    ::= { luxlVoiceVlanMibCompliances 1 }

END
