-- *****************************************************************
-- LUXL-SMI:  Vitesse enterprise structure 
--   
-- Copyright (c) 2002-2013 Vitesse Semiconductor Corporation "Vitesse". 
-- All Rights Reserved.
--   
-- ****************************************************************

LUXL-SMI DEFINITIONS ::= BEGIN

IMPORTS
    MODULE-IDENTITY,
    OBJECT-IDENTITY,
    enterprises
        FROM SNMPv2-SMI;


luxl MODULE-IDENTITY
    LAST-UPDATED    "201309240000Z"
    ORGANIZATION    "Luxul Wireless Corporation"
    CONTACT-INFO
            "support@luxul.com"
    DESCRIPTION
        "The Structure of Management Information for the
        Luxul enterprise."
    REVISION        "201309240000Z"
    DESCRIPTION
        "Initial version of this MIB module."
    ::= { enterprises 6603 }


luxlSwitchMgmt OBJECT-IDENTITY
    STATUS          current
    DESCRIPTION
        "switchMgmt is the root OBJECT IDENTIFIER from
         which object id values are assigned."
    ::= { luxl 1 }



END
