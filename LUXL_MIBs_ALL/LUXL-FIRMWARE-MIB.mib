-- *****************************************************************
-- FIRMWARE-MIB:  Vitesse private MIB
--
-- Copyright (c) 2002-2013 Vitesse Semiconductor Corporation "Vitesse".
-- All Rights Reserved.
--
-- ****************************************************************

LUXL-FIRMWARE-MIB DEFINITIONS ::= BEGIN

IMPORTS
    MODULE-COMPLIANCE, OBJECT-GROUP
        FROM SNMPv2-CONF
    MODULE-IDENTITY, OBJECT-TYPE
        FROM SNMPv2-SMI
    TEXTUAL-CONVENTION
        FROM SNMPv2-TC
    luxlSwitchMgmt
        FROM LUXL-SMI
    Integer32 FROM SNMPv2-SMI
    Unsigned32 FROM SNMPv2-SMI
    TruthValue FROM SNMPv2-TC
    LUXLDisplayString FROM LUXL-TC
    ;

luxlFirmwareMib MODULE-IDENTITY
    LAST-UPDATED "201412160000Z"
    ORGANIZATION
        "Vitesse Semiconductor Corporation"
    CONTACT-INFO
        "Application support <application_support@vitesse.com>"
    DESCRIPTION
        "This is a private version of Firmware"
    REVISION    "201412160000Z"
    DESCRIPTION
        "Add switch table"
    REVISION    "201410100000Z"
    DESCRIPTION
        "Editorial changes"
    REVISION    "201407010000Z"
    DESCRIPTION
        "Initial version"
    ::= { luxlSwitchMgmt 28 }


LUXLFirmwareStatusImageEnum ::= TEXTUAL-CONVENTION
    STATUS      current
    DESCRIPTION
        "This enumeration defines the type of image for status."
    SYNTAX      INTEGER { bootloader(0), activeFirmware(1), alternativeFirmware(2) }

LUXLFirmwareUploadImageEnum ::= TEXTUAL-CONVENTION
    STATUS      current
    DESCRIPTION
        "This enumeration defines the type of image to upload."
    SYNTAX      INTEGER { bootloader(0), firmware(1) }

LUXLFirmwareUploadStatusEnum ::= TEXTUAL-CONVENTION
    STATUS      current
    DESCRIPTION
        "This enumeration defines the status of upload operation."
    SYNTAX      INTEGER { none(0), success(1), inProgress(2), errIvalidIp(3), errTftpFailed(4), errBusy(5), errMemoryInsufficient(6), errInvalidImage(7), errWriteFlash(8), errSameImageExisted(9), errUnknownImage(10), errFlashImageNotFound(11), errFlashEntryNotFound(12), errCrc(13), errImageSize(14), errEraseFlash(15), errIncorrectImageVersion(16), errDownloadUrl(17), errInvalidUrl(18) }

luxlFirmwareMibObjects OBJECT IDENTIFIER
    ::= { luxlFirmwareMib 1 }

luxlFirmwareStatus OBJECT IDENTIFIER
    ::= { luxlFirmwareMibObjects 3 }

luxlFirmwareStatusImageTable OBJECT-TYPE
    SYNTAX      SEQUENCE OF LUXLFirmwareStatusImageEntry
    MAX-ACCESS  not-accessible
    STATUS      current
    DESCRIPTION 
        "This is a table of status of images in flash."
    ::= { luxlFirmwareStatus 1 }

luxlFirmwareStatusImageEntry OBJECT-TYPE
    SYNTAX      LUXLFirmwareStatusImageEntry
    MAX-ACCESS  not-accessible
    STATUS      current
    DESCRIPTION 
        "Each entry has a set of image status."
    INDEX       { luxlFirmwareStatusImageNumber }
    ::= { luxlFirmwareStatusImageTable 1 }

LUXLFirmwareStatusImageEntry ::= SEQUENCE {
    luxlFirmwareStatusImageNumber   Integer32,
    luxlFirmwareStatusImageType     LUXLFirmwareStatusImageEnum,
    luxlFirmwareStatusImageName     LUXLDisplayString,
    luxlFirmwareStatusImageVersion      LUXLDisplayString,
    luxlFirmwareStatusImageBuiltDate    LUXLDisplayString,
    luxlFirmwareStatusImageCodeRevision     LUXLDisplayString
}

luxlFirmwareStatusImageNumber OBJECT-TYPE
    SYNTAX      Integer32 (0..2)
    MAX-ACCESS  not-accessible
    STATUS      current
    DESCRIPTION 
        "The number of image. The number starts from 0."
    ::= { luxlFirmwareStatusImageEntry 1 }

luxlFirmwareStatusImageType OBJECT-TYPE
    SYNTAX      LUXLFirmwareStatusImageEnum
    MAX-ACCESS  read-only
    STATUS      current
    DESCRIPTION 
        "Image type of the status. bootloader(0) is for boot loader.
         activeFirmware(1) is for active (primary) firmware.
         alternativeFirmware(2) is for alternative (backup) firmware."
    ::= { luxlFirmwareStatusImageEntry 2 }

luxlFirmwareStatusImageName OBJECT-TYPE
    SYNTAX      LUXLDisplayString (SIZE(0..127))
    MAX-ACCESS  read-only
    STATUS      current
    DESCRIPTION 
        "Image name."
    ::= { luxlFirmwareStatusImageEntry 3 }

luxlFirmwareStatusImageVersion OBJECT-TYPE
    SYNTAX      LUXLDisplayString (SIZE(0..255))
    MAX-ACCESS  read-only
    STATUS      current
    DESCRIPTION 
        "Image version."
    ::= { luxlFirmwareStatusImageEntry 4 }

luxlFirmwareStatusImageBuiltDate OBJECT-TYPE
    SYNTAX      LUXLDisplayString (SIZE(0..255))
    MAX-ACCESS  read-only
    STATUS      current
    DESCRIPTION 
        "The built date when the image is built."
    ::= { luxlFirmwareStatusImageEntry 5 }

luxlFirmwareStatusImageCodeRevision OBJECT-TYPE
    SYNTAX      LUXLDisplayString (SIZE(0..127))
    MAX-ACCESS  read-only
    STATUS      current
    DESCRIPTION 
        "The code revesion which the image is built."
    ::= { luxlFirmwareStatusImageEntry 6 }

luxlFirmwareStatusImageUpload OBJECT IDENTIFIER
    ::= { luxlFirmwareStatus 2 }

luxlFirmwareStatusImageUploadStatus OBJECT-TYPE
    SYNTAX      LUXLFirmwareUploadStatusEnum
    MAX-ACCESS  read-only
    STATUS      current
    DESCRIPTION 
        "The status indicates the status of current upload operation. It is
         updated automatically. Modifying this flag does not take any effect.
         none(0) means no upload operation. success(1) means upload operation is
         successful. inProgress(2) means current upload operation is in
         progress. errIvalidIp(3) means upload operation is failed due to
         invalid IP address. errTftpFailed(4) means upload operation is failed
         due to failed TFTP operation. errBusy(5) means upload operation is
         failed due to other upload in processing. errMemoryInsufficient(6)
         means upload operation is failed due to memory insufficient.
         errInvalidImage(7) means upload operation is failed due to invalid
         image. errWriteFlash(8) means upload operation is failed due to failed
         writing flash. errSameImageExisted(9) means upload operation is failed
         because the upload image is the same as the one in flash.
         errUnknownImage(10) means upload operation is failed because the type
         of upload image is unknown. errFlashImageNotFound(11) means upload
         operation is failed because the location in flash to upload the image
         is not found. errFlashEntryNotFound(12) means upload operation is
         failed because the corresponding entry in flash to upload the image is
         not found. errCrc(13) means upload operation is failed due to incorrect
         CRC in the upload image. errImageSize(14) means upload operation is
         failed due to invalid image size. errEraseFlash(15) means upload
         operation is failed due to failed erasing flash.
         errIncorrectImageVersion(16) means upload operation is failed due to
         incorrect version of the upload image. errDownloadUrl(17) means upload
         operation is failed due to fail to download image from URL.
         errInvalidUrl(18) means upload operation is failed due to invalid URL. "
    ::= { luxlFirmwareStatusImageUpload 1 }

luxlFirmwareStatusSwitchTable OBJECT-TYPE
    SYNTAX      SEQUENCE OF LUXLFirmwareStatusSwitchEntry
    MAX-ACCESS  not-accessible
    STATUS      current
    DESCRIPTION 
        "This is a table of status of images in switch."
    ::= { luxlFirmwareStatus 3 }

luxlFirmwareStatusSwitchEntry OBJECT-TYPE
    SYNTAX      LUXLFirmwareStatusSwitchEntry
    MAX-ACCESS  not-accessible
    STATUS      current
    DESCRIPTION 
        "Each entry has a set of image status."
    INDEX       { luxlFirmwareStatusSwitchSwitchId }
    ::= { luxlFirmwareStatusSwitchTable 1 }

LUXLFirmwareStatusSwitchEntry ::= SEQUENCE {
    luxlFirmwareStatusSwitchSwitchId    Integer32,
    luxlFirmwareStatusSwitchChipId      LUXLDisplayString,
    luxlFirmwareStatusSwitchBoardType   LUXLDisplayString,
    luxlFirmwareStatusSwitchPortCnt     Unsigned32,
    luxlFirmwareStatusSwitchProduct     LUXLDisplayString,
    luxlFirmwareStatusSwitchVersion     LUXLDisplayString,
    luxlFirmwareStatusSwitchBuiltDate   LUXLDisplayString
}

luxlFirmwareStatusSwitchSwitchId OBJECT-TYPE
    SYNTAX      Integer32 (1..16)
    MAX-ACCESS  not-accessible
    STATUS      current
    DESCRIPTION 
        "The ID of switch."
    ::= { luxlFirmwareStatusSwitchEntry 1 }

luxlFirmwareStatusSwitchChipId OBJECT-TYPE
    SYNTAX      LUXLDisplayString (SIZE(0..31))
    MAX-ACCESS  read-only
    STATUS      current
    DESCRIPTION 
        "ID of chip."
    ::= { luxlFirmwareStatusSwitchEntry 2 }

luxlFirmwareStatusSwitchBoardType OBJECT-TYPE
    SYNTAX      LUXLDisplayString (SIZE(0..63))
    MAX-ACCESS  read-only
    STATUS      current
    DESCRIPTION 
        "Type of board."
    ::= { luxlFirmwareStatusSwitchEntry 3 }

luxlFirmwareStatusSwitchPortCnt OBJECT-TYPE
    SYNTAX      Unsigned32
    MAX-ACCESS  read-only
    STATUS      current
    DESCRIPTION 
        "Count of ports."
    ::= { luxlFirmwareStatusSwitchEntry 4 }

luxlFirmwareStatusSwitchProduct OBJECT-TYPE
    SYNTAX      LUXLDisplayString (SIZE(0..63))
    MAX-ACCESS  read-only
    STATUS      current
    DESCRIPTION 
        "Product name."
    ::= { luxlFirmwareStatusSwitchEntry 5 }

luxlFirmwareStatusSwitchVersion OBJECT-TYPE
    SYNTAX      LUXLDisplayString (SIZE(0..255))
    MAX-ACCESS  read-only
    STATUS      current
    DESCRIPTION 
        "Image version."
    ::= { luxlFirmwareStatusSwitchEntry 6 }

luxlFirmwareStatusSwitchBuiltDate OBJECT-TYPE
    SYNTAX      LUXLDisplayString (SIZE(0..255))
    MAX-ACCESS  read-only
    STATUS      current
    DESCRIPTION 
        "The built date when the image is built."
    ::= { luxlFirmwareStatusSwitchEntry 7 }

luxlFirmwareControl OBJECT IDENTIFIER
    ::= { luxlFirmwareMibObjects 4 }

luxlFirmwareControlGlobals OBJECT IDENTIFIER
    ::= { luxlFirmwareControl 1 }

luxlFirmwareControlGlobalsSwapFirmware OBJECT-TYPE
    SYNTAX      TruthValue
    MAX-ACCESS  read-write
    STATUS      current
    DESCRIPTION 
        "Swap firmware between active (primary) and alternative (backup). true
         is to swap the firmware. false is to do nothing."
    ::= { luxlFirmwareControlGlobals 1 }

luxlFirmwareControlImageUpload OBJECT IDENTIFIER
    ::= { luxlFirmwareControl 2 }

luxlFirmwareControlImageUploadDoUpload OBJECT-TYPE
    SYNTAX      TruthValue
    MAX-ACCESS  read-write
    STATUS      current
    DESCRIPTION 
        "Action to do upload image or not. true is to do the upload operation.
         false is to do nothing. The upload operation may need longer time to
         upload the image, so the SNMP timeout time needs to be modified
         accordingly."
    ::= { luxlFirmwareControlImageUpload 1 }

luxlFirmwareControlImageUploadImageType OBJECT-TYPE
    SYNTAX      LUXLFirmwareUploadImageEnum
    MAX-ACCESS  read-write
    STATUS      current
    DESCRIPTION 
        "Type of image to upload. bootloader(0) is to upload bootloader.
         firmware(1) is to upload application firmware."
    ::= { luxlFirmwareControlImageUpload 2 }

luxlFirmwareControlImageUploadUrl OBJECT-TYPE
    SYNTAX      LUXLDisplayString (SIZE(0..255))
    MAX-ACCESS  read-write
    STATUS      current
    DESCRIPTION 
        "The location of image to upload. It is a specific character string that
         constitutes a reference to a resource. Syntax:
         <protocol>://[<username>[:<password>]@]<host>[:<port>][/<path>]/<file_name>
         For example, tftp://10.10.10.10/new_image_path/new_image.dat,
         http://username:password@10.10.10.10:80/new_image_path/new_image.dat. A
         valid file name is a text string drawn from alphabet (A-Za-z), digits
         (0-9), dot (.), hyphen (-), under score(_). The maximum length is 63
         and hyphen must not be first character. The file name content that only
         contains '.' is not allowed."
    ::= { luxlFirmwareControlImageUpload 3 }

luxlFirmwareMibConformance OBJECT IDENTIFIER
    ::= { luxlFirmwareMib 2 }

luxlFirmwareMibCompliances OBJECT IDENTIFIER
    ::= { luxlFirmwareMibConformance 1 }

luxlFirmwareMibGroups OBJECT IDENTIFIER
    ::= { luxlFirmwareMibConformance 2 }

luxlFirmwareStatusImageTableInfoGroup OBJECT-GROUP
    OBJECTS     { luxlFirmwareStatusImageType, luxlFirmwareStatusImageName, 
                  luxlFirmwareStatusImageVersion, 
                  luxlFirmwareStatusImageBuiltDate, 
                  luxlFirmwareStatusImageCodeRevision }
    STATUS      current
    DESCRIPTION
        "A collection of objects suitable for bulk operations."
    ::= { luxlFirmwareMibGroups 1 }

luxlFirmwareStatusImageUploadInfoGroup OBJECT-GROUP
    OBJECTS     { luxlFirmwareStatusImageUploadStatus }
    STATUS      current
    DESCRIPTION
        "A collection of objects suitable for bulk operations."
    ::= { luxlFirmwareMibGroups 2 }

luxlFirmwareStatusSwitchTableInfoGroup OBJECT-GROUP
    OBJECTS     { luxlFirmwareStatusSwitchChipId, 
                  luxlFirmwareStatusSwitchBoardType, 
                  luxlFirmwareStatusSwitchPortCnt, 
                  luxlFirmwareStatusSwitchProduct, 
                  luxlFirmwareStatusSwitchVersion, 
                  luxlFirmwareStatusSwitchBuiltDate }
    STATUS      current
    DESCRIPTION
        "A collection of objects suitable for bulk operations."
    ::= { luxlFirmwareMibGroups 3 }

luxlFirmwareControlGlobalsInfoGroup OBJECT-GROUP
    OBJECTS     { luxlFirmwareControlGlobalsSwapFirmware }
    STATUS      current
    DESCRIPTION
        "A collection of objects suitable for bulk operations."
    ::= { luxlFirmwareMibGroups 4 }

luxlFirmwareControlImageUploadInfoGroup OBJECT-GROUP
    OBJECTS     { luxlFirmwareControlImageUploadDoUpload, 
                  luxlFirmwareControlImageUploadImageType, 
                  luxlFirmwareControlImageUploadUrl }
    STATUS      current
    DESCRIPTION
        "A collection of objects suitable for bulk operations."
    ::= { luxlFirmwareMibGroups 5 }

luxlFirmwareMibCompliance MODULE-COMPLIANCE
    STATUS      current
    DESCRIPTION
        "The compliance statement for the implementation."

    MODULE      -- this module

        MANDATORY-GROUPS        { luxlFirmwareStatusImageTableInfoGroup, 
                  luxlFirmwareStatusImageUploadInfoGroup, 
                  luxlFirmwareStatusSwitchTableInfoGroup, 
                  luxlFirmwareControlGlobalsInfoGroup, 
                  luxlFirmwareControlImageUploadInfoGroup }

    ::= { luxlFirmwareMibCompliances 1 }

END
